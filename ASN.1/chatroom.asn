-- Specification of a simple chatroom protocol
-- You can use EXTENSIBILITY IMPLIED instead
-- of putting ellipsis (...) everywhere

ChatRoomProtocol DEFINITIONS ::= BEGIN

    User ::= SEQUENCE {
        id             OBJECT IDENTIFIER,
        email          UTF8String (SIZE(1..40)),
        username       UTF8String (SIZE(1..40)),
        ...
    }

    RoomType ::= CHOICE {
        private    [0] NULL,
        public     [1] NULL
    }

    Room ::= SEQUENCE {
        id             OBJECT IDENTIFIER,
        name           UTF8String (SIZE(1..40)),
        type           RoomType
    }

    Message ::= SEQUENCE {
        id             OBJECT IDENTIFIER,
        user           User,
        room           Room,
        timestamp      UTCTime,
        message        UTF8String (SIZE(1..128))
    }

END
